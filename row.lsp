(defun row::make-row  (solid)
  (setq	ribs	 (estr::squeeze (estr::get-ribs solid))
	_type	 (infer-type solid ribs)
	material (estr::layer solid)
	dims	 (if (car _type)
		   (car _type)
		   (msr::succesive-measurement solid))
	note	 (cadr _type))
  (estr::del-entities ribs)
  (list	material
	dims
	(cons note
	      (estr::volume solid))
	1
	(list (vla-get-handle (vlax-ename->vla-object solid)))
	(estr::principal-moments solid)))

(defun row::material  (row)
  (car row))
(defun row::dims  (row)
  (cadr row))
(defun row::type  (row)
  (caaddr row))
(defun row::volume  (row)
  (cdaddr row))
(defun row::qty	 (row)
  (cadddr row))
(defun row::id	(row)
  (nth 4 row))
(defun row::principal-moments  (row)
  (nth 5 row))
(defun row::key	 (row)
  (strcat (strcase (row::material row) t)
	  (row::dims->str (row::dims row) "")
	  (row::type row)))
(defun row::dims->str  (dims delimiter)
  (strcat (itoa (car dims))
	  delimiter
	  (itoa (caddr dims))
	  delimiter
	  (itoa (cadr dims))))

(defun row::eq	(row1 row2)
  (and (= (row::key row1) (row::key row2))
       (equal (/ (row::volume row1) 1e6)
	      (/ (row::volume row2) 1e6)
	      *epsilon*)
       (util::uo-list=
	  (row::principal-moments row1)
	  (row::principal-moments row2)
	  1)))

(defun row::<  (row1 row2)
  (< (row::key row1) (row::key row2)))

(defun row::1+	(row)
  (list	(row::material row)
	(row::dims row)
	(cons (row::type row)
	      (row::volume row))
	(1+ (row::qty row))
	(row::principal-moments row)))

(defun row::+  (row-1 row-2)
  (list	(row::material row-1)
	(row::dims row-1)
	(cons (row::type row-1)
	      (row::volume row-1))
	(+ (row::qty row-1) (row::qty row-2))
	(append (row::id row-1) (row::id row-2))
	(row::principal-moments row-1)))
