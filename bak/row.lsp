(defun row::make-row  (solid)
  (setq	ribs	 (estr::squeeze (estr::get-ribs solid))
	_type	 (infer-type solid ribs)
	material (estr::layer solid)
	dims	 (if (car _type)
		   (car _type)
		   (msr::succesive-measurement solid))
	note	 (cadr _type))
  (estr::del-entities ribs)
  (list	material
	dims
	(cons note
	      (estr::volume solid))
	1))

(defun row::material  (row)
  (car row))
(defun row::dims  (row)
  (cadr row))
(defun row::type  (row)
  (caaddr row))
(defun row::volume  (row)
  (cdaddr row))
(defun row::qty	 (row)
  (cadddr row))
(defun row::key	 (row)
  (strcat (strcase (row::material row) T)
	  (row::dims->str (row::dims row) "")
	  (row::type row)))
(defun row::dims->str  (dims delimiter)
  (strcat (itoa (car dims))
	  delimiter
	  (itoa (cadr dims))
	  delimiter
	  (itoa (caddr dims))))

(defun row::eq	(row1 row2)
  (and (= (row::key row1) (row::key row2))
       (equal (/ (row::volume row1) 1e6)
	      (/ (row::volume row2) 1e6)
	      1e-2)))

(defun row::<  (row1 row2)
  (< (row::key row1) (row::key row2)))

(defun row::1+	(row)
  (list	(row::material row)
	(row::dims row)
	(cons (row::type row)
	      (row::volume row))
	(1+ (row::qty row))))
